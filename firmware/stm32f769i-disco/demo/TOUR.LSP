; A short tour of cities (name list at the top: change it).
(load "LIB.LSP")
(layers 95)
(view 20 0 1)
(foreach place '("Berlin" "Rome" "Cairo" "Nairobi" "Mumbai" "Singapore")
  (note (strcat "Trip to " place))
  (hop place 5 4500)
  (hold 1500))
(note "Back out and spin")
(fly 20 0 1 3000)
(spin T 20)
(hold 3000)
